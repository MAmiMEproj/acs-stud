# sys-reqs

## #1: COM (Container)
вимоги до комунікації

### #3: Com.components (Functional)
програмна композиція повинна налічувати компонент комунікації з апаратним успадкуванням

### #5: IO structure (Functional)
прграмна композиція повинна забезпечувати комунікацію з апаратним успадкуванням у двосторонньому порядку.
Вона повинна мати змогу передавати на апаратне забезпечення велечину заповниності ШІМ (у проміжку від 0 до 100 включаючи крайні значення) з точністю до 1% у від діапазону
Також вона повинна зчитувати значення кута та кутової швидкості двигуна з точністю не нижче 0.01 градуса та 0.01 с відповідно

## #2: SREAD (Functional)
Компонент Scanner Read повинен зчитувати значення кутової швидкості з апаратного забезпечення через комунікаційний компонент і перетворювати його у формат, придатний для читання компонентом двигуна.
- Keywords: mt

### #9: MCON (Functional)

#### #10: Motor control-out (Functional)
програмна композиція повинна містити засоби управління двигуном по напрямку та швидкості.
напрямлк визначається двома можливими значеннями: (Ліво ,право)
за велечинами 0 та 1 відповідно.
Зупинка двигуна заюезпечується швидкістю.
Швидкість двигуна передається на апаратне успадкування у якості заповнення скважності ШІМ у ріадазоні 0 - 100 включаючи крайні значення. Точність не повинна бути меншою за 0.01% загального діапазона значення

## #7: CON (Functional)
Цей компонент є інтегратором керування, куди входить перехідний формат. Цей компонент порівнює бажане значення з фактичним значенням і адресує його компоненту двигуна.

## #8: HMI (Functional)
Людино-машинний інтерфейс повинен забезпечувати зв’язок у режимі реального часу між simulink, апаратним забезпеченням і людиною. Його можна підключити до джойстика або мобільного телефону для керування системою.
